KAZOO-MIB DEFINITIONS ::= BEGIN

IMPORTS
	enterprises, OBJECT-TYPE, MODULE-IDENTITY,
	Integer32, Gauge32, Counter32, Counter64, TimeTicks
		FROM SNMPv2-SMI
	DisplayString, DateAndTime
       		FROM SNMPv2-TC
	InetAddressType, InetAddress
       		FROM INET-ADDRESS-MIB
	MODULE-COMPLIANCE, OBJECT-GROUP, NOTIFICATION-GROUP
        	FROM SNMPv2-CONF
;

kazoo MODULE-IDENTITY
	LAST-UPDATED "20130703"
	ORGANIZATION "2600hz.com"
	CONTACT-INFO
		"web: http://www.2600hz.com email: info@2600hz.com"
	DESCRIPTION
		"This MIB module allows monitoring of a Kazoo server"
	REVISION "1"
	DESCRIPTION "First version"
	::= { enterprises 700001 }

core OBJECT IDENTIFIER ::= { kazoo 1 }

identity OBJECT IDENTIFIER ::= { core 1 }

groups OBJECT IDENTIFIER ::= { core 200 }

kazoo-ver OBJECT-TYPE
	SYNTAX      DisplayString
	MAX-ACCESS  read-only
	STATUS      current
	DESCRIPTION "Version of Kazoo"
	::= { identity 1 }

vm OBJECT IDENTIFIER ::= { core 2 }

vm-statistics OBJECT-TYPE
	SYNTAX      SEQUENCE OF Vm-statistics-entry
	MAX-ACCESS  not-accessible
        STATUS      current
	DESCRIPTION "Table listing erlang VMs in cluster with basic stats."
	::= { vm 1 }

vm-statistics-entry OBJECT-TYPE
	SYNTAX		Vm-statistics-entry
	MAX-ACCESS  not-accessible
        STATUS      current
        DESCRIPTION "An erlang VM in the Kazoo cluster"
        INDEX   { nodename }
        ::= { vm-statistics 1 }

Vm-statistics-entry ::= SEQUENCE {
	nodename	OCTET STRING,
	erlang-version	OCTET STRING,
	memory-total	Gauge32,
	memory-processes Gauge32,
	memory-system	Gauge32,
	memory-atom	Gauge32,
	memory-binary	Gauge32,
	memory-code	Gauge32,
	memory-ets	Gauge32,
	amqp-error	Gauge32,
	amqp-request	Gauge32,
	bigcouch-504-error Gauge32,
	bigcouch-other-error Gauge32,
	bigcouch-request Gauge32
}

nodename OBJECT-TYPE
        SYNTAX          OCTET STRING
        MAX-ACCESS      read-only
        STATUS          current
        DESCRIPTION     "Name of the node"
        ::= { vm-statistics-entry 1 }

erlang-version OBJECT-TYPE
        SYNTAX          OCTET STRING
        MAX-ACCESS      read-only
        STATUS          current
        DESCRIPTION     "Erlang version"
        ::= { vm-statistics-entry 2 }

memory-total OBJECT-TYPE
        SYNTAX          Gauge32
        MAX-ACCESS      read-only
        STATUS          current
        DESCRIPTION     "Total memory"
        ::= { vm-statistics-entry 3 }

memory-processes OBJECT-TYPE
        SYNTAX          Gauge32
        MAX-ACCESS      read-only
        STATUS          current
        DESCRIPTION     "Memory used by processes"
        ::= { vm-statistics-entry 4 }

memory-system OBJECT-TYPE
        SYNTAX          Gauge32
        MAX-ACCESS      read-only
        STATUS          current
        DESCRIPTION     "Memory used by system"
        ::= { vm-statistics-entry 5 }

memory-atom OBJECT-TYPE
        SYNTAX          Gauge32
        MAX-ACCESS      read-only
        STATUS          current
        DESCRIPTION     "Memory used by atom"
        ::= { vm-statistics-entry 6 }

memory-binary OBJECT-TYPE
        SYNTAX          Gauge32
        MAX-ACCESS      read-only
        STATUS          current
        DESCRIPTION     "Memory used by binary"
        ::= { vm-statistics-entry 7 }

memory-code OBJECT-TYPE
        SYNTAX          Gauge32
        MAX-ACCESS      read-only
        STATUS          current
        DESCRIPTION     "Memory used by code"
        ::= { vm-statistics-entry 8 }

memory-ets OBJECT-TYPE
        SYNTAX          Gauge32
        MAX-ACCESS      read-only
        STATUS          current
        DESCRIPTION     "Memory used by ets"
        ::= { vm-statistics-entry 9 }

amqp-error OBJECT-TYPE
        SYNTAX          Gauge32
        MAX-ACCESS      read-only
        STATUS          current
        DESCRIPTION     "Amqp errors for start_amqp"
        ::= { vm-statistics-entry 10 }

amqp-request OBJECT-TYPE
        SYNTAX          Gauge32
        MAX-ACCESS      read-only
        STATUS          current
        DESCRIPTION     "Amqp requests"
        ::= { vm-statistics-entry 11 }

bigcouch-504-error OBJECT-TYPE
        SYNTAX          Gauge32
        MAX-ACCESS      read-only
        STATUS          current
        DESCRIPTION     "504 errors from bigcouch requests"
        ::= { vm-statistics-entry 12 }

bigcouch-other-error OBJECT-TYPE
        SYNTAX          Gauge32
        MAX-ACCESS      read-only
        STATUS          current
        DESCRIPTION     "Other errors from bigcouch requests"
        ::= { vm-statistics-entry 13 }

bigcouch-request OBJECT-TYPE
        SYNTAX          Gauge32
        MAX-ACCESS      read-only
        STATUS          current
        DESCRIPTION     "Number of bigcouch requests"
        ::= { vm-statistics-entry 14 }

ecallmgr OBJECT IDENTIFIER ::= { core 3 }

ecallmgr-tab OBJECT-TYPE
        SYNTAX      SEQUENCE OF Ecallmgr-entry
        MAX-ACCESS  not-accessible
        STATUS      current
        DESCRIPTION "Table listing ecallmgrs and stats"
        ::= { ecallmgr 1 }

ecallmgr-entry OBJECT-TYPE
        SYNTAX      Ecallmgr-entry
        MAX-ACCESS  not-accessible
        STATUS      current
        DESCRIPTION "An ecallmgr process in the cluster"
        INDEX   { ec-nodename }
        ::= { ecallmgr-tab 1 }

Ecallmgr-entry ::= SEQUENCE {
        ec-nodename	OCTET STRING,
	ec-reduction	Gauge32,
	ec-processes	Gauge32,
	ec-register-attempt Gauge32,
	ec-register-fail Gauge32,
	ec-presence	 Gauge32
}

ec-nodename OBJECT-TYPE
        SYNTAX          OCTET STRING
        MAX-ACCESS      read-only
        STATUS          current
        DESCRIPTION     "Name of the node"
        ::= { ecallmgr-entry 1 }

ec-reduction OBJECT-TYPE
        SYNTAX          Gauge32
        MAX-ACCESS      read-only
        STATUS          current
        DESCRIPTION     "Number of reductions"
        ::= { ecallmgr-entry 2 }

ec-processes OBJECT-TYPE
        SYNTAX          Gauge32
        MAX-ACCESS      read-only
        STATUS          current
        DESCRIPTION     "Number of processes"
        ::= { ecallmgr-entry 3 }

ec-register-attempt OBJECT-TYPE
        SYNTAX          Gauge32
        MAX-ACCESS      read-only
        STATUS          current
        DESCRIPTION     "Number of registration attempts"
        ::= { ecallmgr-entry 4 }

ec-register-fail OBJECT-TYPE
        SYNTAX          Gauge32
        MAX-ACCESS      read-only
        STATUS          current
        DESCRIPTION     "Number of registration failures"
        ::= { ecallmgr-entry 5 }

ec-presence OBJECT-TYPE
        SYNTAX          Gauge32
        MAX-ACCESS      read-only
        STATUS          current
        DESCRIPTION     "Number of presence attempts"
        ::= { ecallmgr-entry 6 }

sip OBJECT IDENTIFIER ::= { core 4 }

sip-domain OBJECT-TYPE
	SYNTAX	    SEQUENCE OF Sip-domain-entry
	MAX-ACCESS  not-accessible
    	STATUS      current
    	DESCRIPTION "Table listing sip domains defined in Kazoo"
	::= { sip 1 }

sip-domain-entry OBJECT-TYPE
    	SYNTAX      Sip-domain-entry
     	MAX-ACCESS  not-accessible
     	STATUS      current
     	DESCRIPTION "A sip domain defined in Kazoo"
     	INDEX   { sip-domain-name }
     	::= { sip-domain 1 }

Sip-domain-entry ::= SEQUENCE {
    	sip-domain-name	OCTET STRING,
	sip-recovery-expire Gauge32,
	sip-progress-timeout Gauge32,
	sip-unallocated-number Gauge32,
	sip-no-route-destination Gauge32,
	sip-normal-clearing Gauge32,
	sip-originator-cancel Gauge32,
	sip-destination-out-of-order Gauge32,
	sip-requested-chan-unavail Gauge32,
	sip-no-answer Gauge32,
	sip-invalid-number-format Gauge32,
	sip-incompatible-destination Gauge32
}

sip-domain-name OBJECT-TYPE
	SYNTAX		OCTET STRING
	MAX-ACCESS  	read-only
	STATUS      	current
	DESCRIPTION	"Name of the domain"
	::= { sip-domain-entry 1 }

sip-recovery-expire OBJECT-TYPE
	SYNTAX		Gauge32
	MAX-ACCESS  	read-only
	STATUS      	current
	DESCRIPTION	"Recovery expiry for each domain"
	::= { sip-domain-entry 2 }

sip-progress-timeout OBJECT-TYPE
	SYNTAX		Gauge32
	MAX-ACCESS  	read-only
	STATUS      	current
	DESCRIPTION	"Progress timeouts for each domain"
	::= { sip-domain-entry 3 }

sip-unallocated-number OBJECT-TYPE
	SYNTAX      Gauge32
	MAX-ACCESS  read-only
	STATUS      current
	DESCRIPTION "Unallocated number events for domain"
	::= { sip-domain-entry 4 }

sip-no-route-destination OBJECT-TYPE
	SYNTAX      Gauge32
	MAX-ACCESS  read-only
	STATUS      current
	DESCRIPTION "No route to destination events for domain"
	::= { sip-domain-entry 5 }

sip-normal-clearing OBJECT-TYPE
	SYNTAX      Gauge32
	MAX-ACCESS  read-only
	STATUS      current
	DESCRIPTION "Successful calls for domain"
	::= { sip-domain-entry 6 }

sip-originator-cancel OBJECT-TYPE
	SYNTAX      Gauge32
	MAX-ACCESS  read-only
	STATUS      current
	DESCRIPTION "Originator cancel events for domain"
	::= { sip-domain-entry 7 }

sip-destination-out-of-order OBJECT-TYPE
	SYNTAX      Gauge32
	MAX-ACCESS  read-only
	STATUS      current
	DESCRIPTION "Destination out of order events for domain"
	::= { sip-domain-entry 8 }

sip-requested-chan-unavail OBJECT-TYPE
	SYNTAX      Gauge32
	MAX-ACCESS  read-only
	STATUS      current
	DESCRIPTION "No channel available events for domain"
	::= { sip-domain-entry 9 }

sip-no-answer OBJECT-TYPE
	SYNTAX      Gauge32
	MAX-ACCESS  read-only
	STATUS      current
	DESCRIPTION "No answer events for domain"
	::= { sip-domain-entry 10 }

sip-invalid-number-format OBJECT-TYPE
	SYNTAX      Gauge32
	MAX-ACCESS  read-only
	STATUS      current
	DESCRIPTION "Invalid format events for domain"
	::= { sip-domain-entry 11 }

sip-incompatible-destination OBJECT-TYPE
	SYNTAX      Gauge32
	MAX-ACCESS  read-only
	STATUS      current
	DESCRIPTION "Incompatible destination events for domain"
	::= { sip-domain-entry 12 }

allgroup OBJECT-GROUP
	OBJECTS { sip-domain-name, ec-presence, ec-register-fail,
		ec-register-attempt, ec-processes, ec-reduction, ec-nodename,
		memory-ets, memory-code, memory-binary, memory-atom,
		memory-system, memory-processes, memory-total,
		erlang-version, nodename,
		 sip-unallocated-number, sip-progress-timeout,
		sip-recovery-expire, kazoo-ver, sip-normal-clearing,
		sip-no-route-destination, bigcouch-other-error,
		bigcouch-504-error, amqp-request, amqp-error, sip-no-answer,
		sip-requested-chan-unavail, sip-destination-out-of-order,
		sip-originator-cancel, sip-incompatible-destination,
		sip-invalid-number-format, bigcouch-request
	}
	STATUS  current
	DESCRIPTION "Various snmp oids"
	::= { groups 1 }
END
